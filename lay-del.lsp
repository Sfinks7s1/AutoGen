;;;---Удаление НЕпечатных слоев.
;;;
(defun c:dlnp ( / e:list e:lay e:noprint)
  (command "_layer" "on" "0" "thaw" "0" "u" "0" "set" "0" "")
  (setq e:list(tblnext "layer" T))
  (setq e:lay (cdr (assoc 2 e:list)))
  (setq e:noprint (cdr(assoc 290 (entget(tblobjname "layer" e:lay)))))
  (if (equal 0 e:noprint)
    (if (not (equal (strcase e:lay T) "defpoints"))
      (command "laydel" "n" e:lay "" "y")
    )
  )
  (while
    (setq e:list(tblnext "layer"))
    (setq e:lay (cdr (assoc 2 e:list)))
    (setq e:noprint (cdr(assoc 290 (entget(tblobjname "layer" e:lay)))))
    (if (equal 0 e:noprint)
      (if (not (equal (strcase e:lay T) "defpoints"))
      (command "laydel" "n" e:lay "" "y")
      )
    )
  )
)
;;;---Удаление Замороженных и Отключенных слоев.
;;;
(defun c:dlfo ( / e:list e:lay e:fr e:of)
  (setq e:list(tblnext "layer" T))
  (setq e:lay (cdr (assoc 2 e:list)))
  (setq e:fr (cdr (assoc 70 e:list)))
  (setq e:of (cdr (assoc 62 e:list)))
  (if (and(equal 1 e:fr)(< e:of 0))
    (if (not (equal (strcase e:lay T) "defpoints"))
      (command "laydel" "n" e:lay "" "y")
    )
  )
  (while
    (setq e:list(tblnext "layer"))
    (setq e:lay (cdr (assoc 2 e:list)))
    (setq e:fr (cdr (assoc 70 e:list)))
    (setq e:of (cdr (assoc 62 e:list)))
    (if (and(equal 1 e:fr)(< e:of 0))
      (if (not (equal (strcase e:lay T) "defpoints"))
        (command "laydel" "n" e:lay "" "y")
      )
    )
  )
)
;;; Удаление замороженных слоев
(defun c:dlf ( / e:list e:lay e:fr)
  (setq e:list(tblnext "layer" T))
  (setq e:lay (cdr (assoc 2 e:list)))
  (setq e:fr (cdr (assoc 70 e:list)))
  (if (equal 1 e:fr)
    (if (not (equal (strcase e:lay T) "defpoints"))
      (command "laydel" "n" e:lay "" "y")
    )
  )
  (while
    (setq e:list(tblnext "layer"))
    (setq e:lay (cdr (assoc 2 e:list)))
    (setq e:fr (cdr (assoc 70 e:list)))
    (if (equal 1 e:fr)
      (if (not (equal (strcase e:lay T) "defpoints"))
        (command "laydel" "n" e:lay "" "y")
      )
    )
  )
)
;;; Удаление выключенных слоев
(defun c:dlo ( / e:list e:lay e:of)
  (setq e:list(tblnext "layer" T))
  (setq e:lay (cdr (assoc 2 e:list)))
  (setq e:of (cdr (assoc 62 e:list)))
  (if (< e:of 0)
    (if (not (equal (strcase e:lay T) "defpoints"))
      (command "laydel" "n" e:lay "" "y")
    )
  )
  (while
    (setq e:list(tblnext "layer"))
    (setq e:lay (cdr (assoc 2 e:list)))
    (setq e:of (cdr (assoc 62 e:list)))
    (if (< e:of 0)
      (if (not (equal (strcase e:lay T) "defpoints"))
        (command "laydel" "n" e:lay "" "y")
      )
    )
  )
)
;;; Удаление текущего слоя
(defun c:dlc ( / e:lay e:fr)
  (setq e:lay (getvar "clayer"))
  (setvar "clayer" "0")
  (command "laydel" "n" e:lay "" "y")
)
